# -*- coding: utf-8 -*-

import FreeCAD
import os
from PySide import QtGui

macro_path = FreeCAD.ParamGet("User parameter:BaseApp/Preferences/Macro").GetString("MacroPath")
ui_path = "%s/import_with_reference_part_select.ui" % macro_path

class SimpleCopy:
  def __init__(self, obj, originalPart, location, locationRelative):
    obj.addProperty("App::PropertyFile", "location").location = location
    obj.addProperty("App::PropertyString", "originalPartName").originalPartName = originalPart.Name
    obj.addProperty("App::PropertyBool", "locationRelative").locationRelative = locationRelative
    obj.ViewObject.Proxy = 0
    obj.Shape = originalPart.Shape
    obj.Label = originalPart.Label
    obj.ViewObject.ShapeColor = originalPart.ViewObject.ShapeColor
    obj.ViewObject.LineColor = originalPart.ViewObject.LineColor
    obj.ViewObject.PointColor = originalPart.ViewObject.PointColor
    obj.ViewObject.DiffuseColor = originalPart.ViewObject.DiffuseColor

class PartSelectPanel:
  def __init__(self, parts, import_document, actual_document, close_import_document):
    self.parts = parts
    self.import_document = import_document
    self.actual_document = actual_document
    self.close_import_document = close_import_document
    self.form = FreeCADGui.PySideUic.loadUi(ui_path)
    self.form.ImportRelative.setChecked(True)
    
    for part in parts:
     self.form.PartsBox.addItem(part.ViewObject.Icon, part.Label)

  def accept(self):
    selectedPart = [part for part in self.parts if part.Label == self.form.PartsBox.currentText()][0]#
    atOrigin = self.form.AtOrigin.isChecked()
    importRelative = self.form.ImportRelative.isChecked()
    FreeCADGui.Control.closeDialog()
    importPart(self.import_document, self.actual_document, selectedPart, atOrigin, importRelative, self.close_import_document)

  def reject(self):
    FreeCADGui.Control.closeDialog()

    if self.close_import_document:
       closeDocument(self.import_document, self.actual_document)

def openDocumentWhenNeeded(fileName):
  documentAlreadyOpen = fileName in [d.FileName for d in FreeCAD.listDocuments().values()]

  if documentAlreadyOpen:
   doc = [d for d in FreeCAD.listDocuments().values() if d.FileName == fileName][0];
   FreeCAD.Console.PrintMessage("Using already open document %s\n" % doc.Name)
  else:
   FreeCAD.Console.PrintMessage("Opening file %s to import part\n" % fileName)
   doc = FreeCAD.openDocument(fileName)

  return documentAlreadyOpen, doc

def closeDocument(import_document, actual_doc):
  FreeCAD.closeDocument(import_document.Name)
  FreeCAD.setActiveDocument(actual_doc.Name)
  FreeCAD.ActiveDocument = actual_doc

def importPart(import_document, actual_doc, part, atOrigin, importRelative, close_import_document, object_to_replace=None):
  # Create a simple copy and add it to the active document
  obj = actual_doc.addObject('Part::FeaturePython', part.Name)

  if importRelative:
    commonprefix = os.path.commonprefix([actual_doc.FileName, import_document.FileName])
    location = os.path.relpath(import_document.FileName, commonprefix)
  else:
   location = import_document.FileName

  SimpleCopy(obj, part, location, importRelative)

  if atOrigin:
    obj.Placement.Base = FreeCAD.Vector(0, 0, 0)
  elif object_to_replace is not None:
   obj.Placement = object_to_replace.Placement
   actual_doc.removeObject(object_to_replace.Name)
   obj.Label = part.Label

  if close_import_document:
    closeDocument(import_document, actual_document)

  actual_doc.recompute()

def selectPart(fileName):
 FreeCAD.Console.PrintMessage("importing part from %s\n" % (fileName))
 actual_document = FreeCAD.ActiveDocument

 documentAlreadyOpen, doc = openDocumentWhenNeeded(fileName)

 # Get all visible parts and bodys from the document
 visibleObjects = [o for o in doc.findObjects() if o.ViewObject.Visibility and o.TypeId in ("PartDesign::Body" , "App::Part")]

 if len(visibleObjects) == 0:
  QtGui.QMessageBox.information(  QtGui.qApp.activeWindow(), "Import Error", "There where no visible parts or bodies in the selected file.")
 else:
  FreeCAD.Console.PrintMessage("Found %d visible objects\n" %len(visibleObjects))
  panel = PartSelectPanel(visibleObjects, doc, actual_document, not documentAlreadyOpen)
  FreeCADGui.Control.showDialog(panel)

def refreshPart(part):
  FreeCAD.Console.PrintMessage("Refreshing part '%s'\n" % part.Label)
  location = part.location
  actual_document = FreeCAD.ActiveDocument

  if part.locationRelative:
   directory = os.path.dirname(actual_document.FileName)
   location = os.path.join(directory, location).replace('\\', '/')

  FreeCAD.Console.PrintMessage("importing from location '%s'\n" % location)

  documentAlreadyOpen, doc = openDocumentWhenNeeded(location)
  import_part = doc.getObject(part.originalPartName)
  importPart(doc, actual_document, import_part, False, part.locationRelative, not documentAlreadyOpen, part)

# At first we check if something is selected. If so perform a refresh instead of an import
selection = FreeCADGui.Selection.getSelection(FreeCAD.ActiveDocument.Name)

if len(selection) > 0:
  # Perform refresh 
  partnamesWithoutLocation = []

  for p in selection:
    try:
      p.getPropertyByName("location")
    except AttributeError:
      partnamesWithoutLocation.append(p.Label)

  if len(partnamesWithoutLocation) > 0:
   QtGui.QMessageBox.information(  QtGui.qApp.activeWindow(), "Selection Error", "The following selected Objects have no location property set %s. Maybe you selected something that was not imported before?" % partnamesWithoutLocation)
  else:
   for p in selection:
      refreshPart(p)
else:
  # Perform import
  dialog = QtGui.QFileDialog(
   QtGui.qApp.activeWindow(),
   "Select the FreeCAD document you want to import"
  )
  
  dialog.setFileMode(QtGui.QFileDialog.ExistingFile)
  dialog.setNameFilter("FreeCAD Files (*.FCStd)")
  
  if dialog.exec_():
   selectPart(dialog.selectedFiles()[0])
  else:
   FreeCAD.Console.PrintMessage("No File selected. Cancelling operation.")
